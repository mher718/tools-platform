OTSBU-WM-UI-MIB DEFINITIONS ::= BEGIN
--
-- MIB objects for WMUI agent
--
IMPORTS
  MODULE-IDENTITY, OBJECT-TYPE, NOTIFICATION-TYPE,
  Integer32, enterprises
    FROM SNMPv2-SMI
  SnmpAdminString
    FROM SNMP-FRAMEWORK-MIB
  RowStatus, StorageType
    FROM SNMPv2-TC
  InetAddressType, InetAddress
    FROM INET-ADDRESS-MIB;

wmUIMIB MODULE-IDENTITY
  LAST-UPDATED "201503190000Z"
  ORGANIZATION
   "Oberthur Technologies"
  CONTACT-INFO
    "postal: Oberthur Technologies
             Oberthur Technologies Headquarters
             420 rue d Estienne d Orves
             92700 Colombes
             France
     email:  http://www.obertur.com"
  DESCRIPTION
    "MIB module for SNMP trap events triggered by Wallet Manager UI"
  REVISION "201503190000Z"
  DESCRIPTION
   "First draft for Wallet Manager UI MIB"
 ::= { enterprises oberthur(30703) suboid(836685) 401 }

-- Object assignments----------------------------------------------
wmUIObject                 OBJECT IDENTIFIER ::= { wmUIMIB 1 }
wmUITrap                   OBJECT IDENTIFIER ::= { wmUIMIB 2 }
-------------------------------------------------------------------
-- Module Start/Stop (1/2)-----------------------------------------
wmUIStartedNotif NOTIFICATION-TYPE
  STATUS current
  DESCRIPTION
  "Notifies the application state is 'started'"
  ::= { wmUITrap 1 }

wmUIStoppedNotif NOTIFICATION-TYPE
  STATUS current
  DESCRIPTION
  "Notifies the application state is 'stopped'"
  ::= { wmUITrap 2 }
-------------------------------------------------------------------
-- Configuration loading failure/success (3/4) --------------------
wmUIConfig OBJECT-TYPE
  SYNTAX SnmpAdminString
  MAX-ACCESS read-write
  STATUS current
  DESCRIPTION
  "Configuration name that is not loaded"
  ::= { wmUIObject 1 }

wmUIConfigLoadingAlert NOTIFICATION-TYPE
  OBJECTS { wmUIConfig }
  STATUS current
  DESCRIPTION
  "Configuration loading failed"
  ::= { wmUITrap 3 }

wmUIConfigLoadingClear NOTIFICATION-TYPE
  OBJECTS { wmUIConfig }
  STATUS current
  DESCRIPTION
  "Configuration loading successful"
  ::= { wmUITrap 4 }
-------------------------------------------------------------------
-- Database access failure/success (5/6) --------------------------
wmUIDBName OBJECT-TYPE
  SYNTAX SnmpAdminString
  MAX-ACCESS read-write
  STATUS current
  DESCRIPTION
  "Database name"
  ::= { wmUIObject 2 }

wmUIDBDownAlert NOTIFICATION-TYPE
  OBJECTS { wmUIDBName }
  STATUS current
  DESCRIPTION
  "Database access failed"
  ::= { wmUITrap 5 }

wmUIDBUpClear NOTIFICATION-TYPE
  OBJECTS { wmUIDBName }
  STATUS current
  DESCRIPTION
  "Database access successful"
  ::= { wmUITrap 6 }
-------------------------------------------------------------------
-- External Call not responding 11/12 -----------------------------
wmUIClientURL OBJECT-TYPE
  SYNTAX SnmpAdminString
  MAX-ACCESS read-write
  STATUS current
  DESCRIPTION
  "External Client Application URL"
  ::= { wmUIObject 3 }

wmUIExtCallNotRespAlert NOTIFICATION-TYPE
  OBJECTS { wmUIClientURL }
  STATUS current
  DESCRIPTION
  "External Interface with Client Application not responding"
  ::= { wmUITrap 11 }

wmUIExtCallRespClear NOTIFICATION-TYPE
  OBJECTS { wmUIClientURL }
  STATUS current
  DESCRIPTION
  "External Interface with Client Application responding"
  ::= { wmUITrap 12 }
-------------------------------------------------------------------
-- Session Saturation (41/42) -------------------------------------
wmUISessionNum OBJECT-TYPE
  SYNTAX Integer32
  MAX-ACCESS read-write
  STATUS current
  DESCRIPTION
  "Number of sessions"
  ::= { wmUIObject 4 }

wmUISessionSaturationAlert NOTIFICATION-TYPE
  OBJECTS { wmUISessionNum }
  STATUS current
  DESCRIPTION
  "Session (thread) pool saturated"
  ::= { wmUITrap 41 }

wmUISessionNoSaturationClear NOTIFICATION-TYPE
  OBJECTS { wmUISessionNum }
  STATUS current
  DESCRIPTION
  "Session pool not saturated"
  ::= { wmUITrap 42 }
END
